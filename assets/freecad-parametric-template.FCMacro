# Generic FreeCAD parametric block template. Units: mm.
import json
import os
import sys
from pathlib import Path

import FreeCAD as App
import FreeCADGui as Gui
import Part

sys.path.insert(0, str(Path(__file__).with_name("..").joinpath("scripts").resolve()))
from coupon_plate import feature_positions, plate_dims
from print_in_place import pin_z_offset, sleeve_dims, rib_positions, rib_box_dims, joint_grid_positions

# Single source of truth for every dimension. Override the path with the
# PARAMETERS_JSON environment variable to point at a task-specific file;
# defaults to the example shipped alongside this macro.
PARAMETERS_PATH = Path(os.environ.get("PARAMETERS_JSON", Path(__file__).with_name("parameters.example.json")))
with open(PARAMETERS_PATH, "r", encoding="utf-8") as f:
    PARAMETER_DOC = json.load(f)

_sections = ("nominal", "clearances", "derived")
_dupes = set(PARAMETER_DOC.get(_sections[0], {})) & set(PARAMETER_DOC.get(_sections[1], {}))
_dupes |= set(PARAMETER_DOC.get(_sections[0], {})) & set(PARAMETER_DOC.get(_sections[2], {}))
_dupes |= set(PARAMETER_DOC.get(_sections[1], {})) & set(PARAMETER_DOC.get(_sections[2], {}))
if _dupes:
    raise ValueError(f"parameter key(s) {sorted(_dupes)} appear in more than one of nominal/clearances/derived")

PARAMS = {**PARAMETER_DOC["nominal"], **PARAMETER_DOC["clearances"], **PARAMETER_DOC["derived"]}


def add_block(doc, assembly, name, label, shape, xyz, rotate_axis=(1, 0, 0), rotate_deg=0.0, mirror_normal=None):
    if mirror_normal is not None:
        shape = shape.mirror(App.Vector(0, 0, 0), App.Vector(*mirror_normal))
    obj = doc.addObject("PartDesign::Feature", name)
    obj.Label = label
    obj.Shape = shape
    obj.addProperty("App::PropertyVector", "Move", "Assembly").Move = App.Vector(*xyz)
    obj.addProperty("App::PropertyVector", "RotateAxis", "Assembly").RotateAxis = App.Vector(*rotate_axis)
    obj.addProperty("App::PropertyAngle", "RotateDeg", "Assembly").RotateDeg = rotate_deg
    obj.Placement = App.Placement(
        App.Vector(*xyz),
        App.Rotation(App.Vector(*rotate_axis), rotate_deg),
    )
    assembly.addObject(obj)
    return obj


def add_instances(doc, assembly, base_shape, instances):
    """Place one modelled shape at every entry of parameters.json's "instances"
    list (e.g. 4 rover wheels, table legs, screw bosses) — model once, never
    hand-duplicate or hand-rotate geometry per copy. Each entry:
    {"name", "label", "xyz", "rotate_axis" (default [0,0,1]),
     "rotate_deg" (default 0), "mirror_normal" (optional, e.g. [0,1,0])}.
    """
    return [
        add_block(
            doc, assembly,
            spec["name"], spec.get("label", spec["name"]),
            base_shape,
            spec["xyz"],
            rotate_axis=spec.get("rotate_axis", (0, 0, 1)),
            rotate_deg=spec.get("rotate_deg", 0.0),
            mirror_normal=spec.get("mirror_normal"),
        )
        for spec in instances
    ]


def build_coupon_plate(doc, assembly, params_doc, thickness=4.0):
    """Build a small fit-test plate from parameters.json's "test_coupons":
    {"feature": "hole"|"slot", "nominal", "trial_values": [...], "depth"
    (default = plate thickness), "spacing", "margin"}. Print this alone first
    to measure and pick a clearance before committing the full model.
    """
    cfg = params_doc["test_coupons"]
    nominal = cfg["nominal"]
    trial_values = cfg["trial_values"]
    spacing = cfg.get("spacing", 15.0)
    margin = cfg.get("margin", 8.0)
    depth = cfg.get("depth", thickness)

    width, depth_extent = plate_dims(nominal, trial_values, spacing, margin)
    plate = Part.makeBox(width, depth_extent, thickness)

    for x_center, size in feature_positions(nominal, trial_values, spacing, margin):
        y_center = depth_extent / 2
        if cfg["feature"] == "hole":
            cutter = Part.makeCylinder(size / 2, depth, App.Vector(x_center, y_center, 0))
        elif cfg["feature"] == "slot":
            cutter = Part.makeBox(size, nominal * 2, depth, App.Vector(x_center - size / 2, margin, 0))
        else:
            raise ValueError(f"unsupported test_coupons feature {cfg['feature']!r}")
        plate = plate.cut(cutter)

    coupon = doc.addObject("Part::Feature", "CouponPlate")
    coupon.Label = f"Test coupon R{params_doc.get('revision', '')}"
    coupon.Shape = plate
    assembly.addObject(coupon)
    return coupon


def chamfer_cylinder_ends(shape, height, chamfer):
    """Chamfer a cylinder's two circular end edges (not its straight seam
    edge) — used to give a print-in-place pin an easier-to-free lead-in."""
    end_edges = [
        e for e in shape.Edges
        if isinstance(e.Curve, Part.Circle) and (abs(e.Vertexes[0].Point.z) < 1e-6 or abs(e.Vertexes[0].Point.z - height) < 1e-6)
    ]
    return shape.makeChamfer(chamfer, end_edges)


def build_relieved_bore(inner_r, relief_depth, relief_count, relief_width_deg, height):
    """Cavity to cut from a sleeve so its bore stays at inner_r only at
    relief_count evenly spaced flat-box "lands" and opens up to inner_r +
    relief_depth everywhere else — less contact area with the pin than a
    plain full-circle bore, so less friction and less risk of the two
    halves fusing (same reasoning as a herringbone gear bearing's tooth
    contact vs. a ball-in-raceway bearing's point contact). Lands are a
    flat-box approximation of the true arc, good for relief_width_deg <= 30.
    """
    cavity = Part.makeCylinder(inner_r + relief_depth, height)
    for angle in rib_positions(relief_count):
        depth, chord = rib_box_dims(inner_r, relief_depth, relief_width_deg)
        rib = Part.makeBox(depth, chord, height, App.Vector(inner_r, -chord / 2, 0))
        rib = rib.rotate(App.Vector(0, 0, 0), App.Vector(0, 0, 1), angle)
        cavity = cavity.cut(rib)
    return cavity


def build_print_in_place_joint(doc, assembly, params_doc):
    """Build a print-in-place hinge/swivel from parameters.json's
    "print_in_place_joint": {"type": "pin_in_sleeve", "pin_radius",
    "pin_height", "radial_clearance" (default 0.25), "axial_play" (default
    0.3), "wall_thickness" (default "min_wall" clearance or 1.2),
    "standoff_from_bed" (default 1.0), optional "lead_in_chamfer" (mm, pin
    end chamfer), optional "bore_relief": {"count", "width_deg" (default
    20), "depth" (default 0.3)}. See references/print-in-place.md for why
    the joint axis must stay vertical, why radial and axial gaps are kept
    separate, and why it needs a standoff off the bed — this only
    implements "pin_in_sleeve"; extend it the same way for "ball_socket" or
    "living_hinge" when needed.
    """
    cfg = params_doc["print_in_place_joint"]
    if cfg["type"] != "pin_in_sleeve":
        raise NotImplementedError(
            f"print_in_place_joint type {cfg['type']!r} is not implemented — "
            "only 'pin_in_sleeve' is; extend build_print_in_place_joint using it as a template."
        )

    pin_radius = cfg["pin_radius"]
    pin_height = cfg["pin_height"]
    radial_clearance = cfg.get("radial_clearance", 0.25)
    axial_play = cfg.get("axial_play", 0.3)
    wall_thickness = cfg.get("wall_thickness", PARAMS.get("min_wall", 1.2))
    standoff = cfg.get("standoff_from_bed", 1.0)

    inner_r, outer_r, sleeve_h = sleeve_dims(pin_radius, radial_clearance, wall_thickness, pin_height, axial_play)

    pin_shape = Part.makeCylinder(pin_radius, pin_height)
    lead_in_chamfer = cfg.get("lead_in_chamfer")
    if lead_in_chamfer:
        pin_shape = chamfer_cylinder_ends(pin_shape, pin_height, lead_in_chamfer)

    bore_relief = cfg.get("bore_relief")
    if bore_relief:
        cavity = build_relieved_bore(
            inner_r, bore_relief.get("depth", 0.3), bore_relief["count"], bore_relief.get("width_deg", 20.0), sleeve_h
        )
    else:
        cavity = Part.makeCylinder(inner_r, sleeve_h)
    sleeve_shape = Part.makeCylinder(outer_r, sleeve_h).cut(cavity)

    pin = add_block(doc, assembly, "PrintInPlace_Pin", "Print-in-place pin", pin_shape, (0, 0, pin_z_offset(standoff, axial_play)))
    sleeve = add_block(doc, assembly, "PrintInPlace_Sleeve", "Print-in-place sleeve", sleeve_shape, (0, 0, standoff))
    return pin, sleeve


def build_print_in_place_coupon(doc, assembly, params_doc):
    """Build a 2D grid of small pin_in_sleeve joints from parameters.json's
    "print_in_place_joint_coupon": {"pin_radius", "pin_height",
    "wall_thickness", "radial_values": [...], "axial_values": [...],
    "spacing" (auto-sized when omitted), "margin", "standoff_from_bed"}.
    Rows vary radial_clearance, columns vary axial_play, in the order
    given. Print this plate once to find a working combination before
    committing to the full joint — the two parameters interact, so testing
    them one at a time (like test_coupons does) can miss a combination that
    only fails together.
    """
    cfg = params_doc["print_in_place_joint_coupon"]
    pin_radius = cfg["pin_radius"]
    pin_height = cfg["pin_height"]
    wall_thickness = cfg.get("wall_thickness", PARAMS.get("min_wall", 1.2))
    standoff = cfg.get("standoff_from_bed", 1.0)

    positions = joint_grid_positions(
        pin_radius, wall_thickness, cfg["radial_values"], cfg["axial_values"],
        margin=cfg.get("margin", 8.0), spacing=cfg.get("spacing"),
    )
    objs = []
    for i, (x, y, radial, axial) in enumerate(positions):
        inner_r, outer_r, sleeve_h = sleeve_dims(pin_radius, radial, wall_thickness, pin_height, axial)
        pin_shape = Part.makeCylinder(pin_radius, pin_height)
        sleeve_shape = Part.makeCylinder(outer_r, sleeve_h).cut(Part.makeCylinder(inner_r, sleeve_h))
        pin = add_block(doc, assembly, f"Coupon_Pin_{i}", f"Coupon pin r={radial} a={axial}", pin_shape, (x, y, pin_z_offset(standoff, axial)))
        sleeve = add_block(doc, assembly, f"Coupon_Sleeve_{i}", f"Coupon sleeve r={radial} a={axial}", sleeve_shape, (x, y, standoff))
        objs.append((pin, sleeve))
    return objs


doc = App.newDocument("ParametricPrintablePart")
assembly = doc.addObject("App::Part", "Assembly")
assembly.Label = "Movable parametric blocks"

sheet = doc.addObject("Spreadsheet::Sheet", "Parameters")
sheet.set("A1", "PARAMETER")
sheet.set("B1", "VALUE_mm")
for row, key in enumerate(sorted(PARAMS), start=2):
    sheet.set(f"A{row}", key)
    sheet.set(f"B{row}", str(PARAMS[key]))

p = PARAMS
base = add_block(
    doc,
    assembly,
    "Block01_Base",
    "01 Base",
    Part.makeBox(p["base_w"], p["base_d"], p["base_h"]),
    (0, 0, 0),
)

# Replace this example with a locally constructed functional block.
block_shape = Part.makeBox(p["block_w"], p["block_d"], p["block_h"])
block = add_block(
    doc,
    assembly,
    "Block02_Function",
    "02 Functional block",
    block_shape,
    (p["block_x"], p["block_y"], p["block_z"]),
    rotate_axis=(1, 0, 0),
    rotate_deg=p["block_rotate_x"],
)

# Example: repeated-block pattern (e.g. 4 rover wheels, table legs, screw
# bosses) — model the shape once, then place every copy from parameters.json's
# "instances" list. Delete this block if the task has no repeated feature.
if "instances" in PARAMETER_DOC:
    wheel_shape = Part.makeCylinder(p.get("wheel_r", 20.0), p.get("wheel_w", 10.0))
    wheels = add_instances(doc, assembly, wheel_shape, PARAMETER_DOC["instances"])

# Fit-test plate (see build_coupon_plate docstring). Present only when the
# user asked for a coupon before committing the full print.
if "test_coupons" in PARAMETER_DOC:
    coupon = build_coupon_plate(doc, assembly, PARAMETER_DOC)

# Print-in-place hinge/swivel (see build_print_in_place_joint docstring and
# references/print-in-place.md). Present only when the task calls for a
# mechanism that prints already assembled.
if "print_in_place_joint" in PARAMETER_DOC:
    pin, sleeve = build_print_in_place_joint(doc, assembly, PARAMETER_DOC)

# 2D radial x axial fit-test grid for a print-in-place joint (see
# build_print_in_place_coupon docstring). Present only when the user wants
# to test both parameters together before committing to the full joint.
if "print_in_place_joint_coupon" in PARAMETER_DOC:
    coupon_joints = build_print_in_place_coupon(doc, assembly, PARAMETER_DOC)

doc.recompute()
Gui.activeDocument().activeView().viewAxonometric()
Gui.activeDocument().activeView().fitAll()
